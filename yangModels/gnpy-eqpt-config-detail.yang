module gnpy-eqpt-config-detail {
  yang-version 1.1;
  namespace "gnpy:gnpy-eqpt-config-detail";
  // replace with namespace when determined

  prefix "gnpyeqptdetail";

  import gnpy-eqpt-config {
    prefix "geqpt";
  }

  organization
    "Telecom Infra Project OOPT PSE
     Working Group";

  contact
    "WG Web:   <https://github.com/Telecominfraproject/oopt-gnpy>
     WG List:  <mailto:xxx>

     WG Chair: xxx
               <mailto:xxx>

   ";

  description "augment to the base YANG model for gnpy equipment library input for path computation.";

  revision "2018-11-19" {
    description "first draft";
    reference "augment to the base YANG model for equipment library input for path computation with gnpy";
  }

  /*
   * Identities
   */

  identity edfa-type-def {
    description "base identity for variable gain and fixed gain";
  }

  identity variable-gain{
    base edfa-type-def ;
    description "'variable_gain' is a simplified model simulating a 2-coil 
      EDFA with internal, input and output VOAs. The NF vs gain response is calculated 
      accordingly based on the input parameters: nf_min, nf_max, and gain_flatmax. It 
      is not a simple interpolation but a 2-stage NF calculation.";
  }

  identity fixed-gain{
    base edfa-type-def ;
    description "'fixed_gain' is a fixed gain model. NF == Cte == nf0 if gain_min < gain < gain_flatmax";
  }

  identity fiber-variety {
    description "base identity for fiber variety";
  }

  identity SSMF{
    base fiber-variety ;
  }

  identity transceiver-variety {
    description "base identity for transceiver variety";
  }

  identity Voyager {
    base transceiver-variety ;
  }
  
   /*
   * Typedef
   */
    

  

  /*
   *Groupings
   */

  grouping variable-gain {
    leaf nf_min {
      type decimal64 {
        fraction-digits 2;
      }
      units dB;
    }
    leaf nf_max {
      type decimal64 {
        fraction-digits 2;
      }
      units dB;
    }
    leaf out_voa_auto{
      type boolean ;
      description "auto_design feature to optimize the amplifier output VOA. If true, output VOA is present 
      and will be used to push amplifier gain to its maximum, within EOL power margins.";
    }
  }

  grouping fixed-gain{
    leaf nf0 {
      type decimal64 {
        fraction-digits 2;
      }
      units dB;
    }
  }

  grouping no-type-def{

    leaf advanced_config_from_json {
      type string ;
      description " filename with json edfa";
      
    }
  }
  

  grouping openroadm{
    leaf-list nf_coef {
      type decimal64 {
        fraction-digits 5;
      }
      //default [8.1e-4,6.142e-2,1.558,19.97] ;
    }
  }

  augment /geqpt:Edfa {

    leaf allowed_for_design{
      type boolean ;
      description "If false, the amplifier will not be picked by auto-design but it can still be used as a 
      manual input (from JSON or Excel template topology files.)";
    }

    leaf type_def {
      type identityref{
        base edfa-type-def ;
      }
    }

    leaf gain_flatmax {
      type decimal64 {
        fraction-digits 2;
      }
      units dB;
    }
    leaf gain_min {
      type decimal64 {
        fraction-digits 2;
      }
      units dB;
    }
    leaf p_max {
      type decimal64 {
        fraction-digits 2;
      }
      units dBm;
    }
    choice type_of_model {
      case variable-gain {
        when "type_def = 'variable-gain'";
        uses variable-gain ;
      }
      case fixed-gain{
        when "type_def = 'fixed-gain'";
        uses fixed-gain ;
      }
      case no-type-def{
        when "type_def = 'no-type-def'";
        uses no-type-def ;
      }
      case openroadm{
        when "type_def = 'openroadm'";
        uses openroadm ;
      }

    }
  }

  grouping Spans{
    leaf power_mode {
      type boolean ;
    }
    leaf delta_power_range_db {
      type string ;
      default [0,0,0.5] ;
    }
    leaf max_length {
      type decimal64 {
        fraction-digits 2;
      }
      units km;
      default 150.0 ;
    }
    leaf length_units{
      type string ;
      default "km";
    }
    leaf padding{
      type decimal64 {
        fraction-digits 2;
      }
      default 10.0 ;
    }
    leaf EOL{
       type decimal64 {
        fraction-digits 2;
      }
      default 0.0 ;
    }
    leaf conn_in{
      type decimal64 {
        fraction-digits 2;
      }
      default 0.0 ;
    }
    leaf conn_out{
      type decimal64 {
        fraction-digits 2;
      }    
      default 0.0 ;
    }
  }

  grouping Roadms{
    leaf gain_mode_default_loss{
      type decimal64 {
        fraction-digits 2;
      }    
      default 20.0 ;
      description "Default value if Roadm/params/loss is None in the topology input description. This default 
      value is ignored if a params/loss value is input in the topology for a given ROADM.";
    }
    leaf power_mode_pref {
      type decimal64 {
        fraction-digits 2;
      }    
      default -20 ;
      description "Power mode only. Auto-design sets the power of ROADM ingress amplifiers to power_dbm + 
      power_range_db, regardless of existing gain settings from the topology JSON input. Auto-design sets 
      the Roadm loss so that its egress channel power = power_mode_pref, regardless of existing loss settings 
      from the topology JSON input. It means that the ouput power from a ROADM (and therefore its OSNR contribution) 
      is Cte and not depending from power_dbm and power_range_db sweep settings. This choice is meant to 
      reflect some typical control loop algorithms.";
    }
  }

  grouping SI{
    leaf fmin {
      type decimal64 {
        fraction-digits 2;
      }
      default 191300000000000 ;
      units Hz ;
      description "In Hz. Carrier min max excursion";
    }
    leaf fmax {
      type decimal64 {
        fraction-digits 2;
      }
      default 195100000000000 ;
      units Hz ;
      description "In Hz. Carrier min max excursion";
    }
    leaf baud_rate{
      type decimal64 {
          fraction-digits 2;
      }
      default 32000000000 ;
      units baud ;
      description "baud_rate";
    }
    leaf spacing{
      type decimal64 {
          fraction-digits 2;
      }
      default 50000000000 ;
      units Hz ;
      description "In Hz. Carrier spacing.";
    }
    leaf OSNR{
      type decimal64 {
          fraction-digits 2;
      }
      default 11.0 ;
      units dB ;
      description "   Not used.";
    }    
    leaf bit_rate{
      type decimal64 {
          fraction-digits 2;
      }
      default 100000000000 ;
      units bit/s ;
      description "   Not used.";
    }
    leaf roll_off{
      type decimal64 {
          fraction-digits 2;
      }
      default 0.1 ;
      description "   Not used.";
    }
    leaf cost{
      type decimal64 {
          fraction-digits 2;
      }
      default 1 ;
      description "arbitrary unit";
    }
    leaf power_dBm{
      type decimal64 {
          fraction-digits 2;
      }
      default 0.0 ;
      units dBm ;
      description " Reference channel power. In gain mode (see spans/power_mode = false), all gain settings are 
      offset w/r/t this reference power. In power mode, it is the reference power for Spans/delta_power_range_db. 
      For example, if delta_power_range_db = [0,0,0], the same power=power_dbm is launched in every spans. The network 
      design is performed with the power_dbm value: even if a power sweep is defined (see after) the design is not repeated.";
    }
    leaf power_range_db{
      type string ;
      default [0,0,0.5] ;
      units dBm ;
      description " Power sweep excursion around power_dbm. It is not the min and max channel power values! 
      The reference power becomes: power_range_db + power_dbm.";
    }
  }
  
    /*
    * augment
    */


  augment /geqpt:Fiber {
    leaf dispersion{
      type decimal64 {
        fraction-digits 8;
      }
      units s.m-1.m-1;
    }
    leaf gamma{
      type decimal64 {
        fraction-digits 8;
      }
      units w-2.m-1 ;
      description "2pi.n2/(lambda*Aeff) (w-2.m-1)";
    }
    
  }

  augment /geqpt:Transceiver{
    container frequency {
      leaf min {
        type decimal64 {
            fraction-digits 2;
          }
        units Hz ;
      }
      leaf max {
        type decimal64 {
            fraction-digits 2;
          }
        units Hz ;
      }
      description "Min/max frequency of transponder eg 191.35e12  and 196.1e12";
    }
  }
  augment /geqpt:Transceiver/geqpt:mode{
    leaf baud_rate{
      type decimal64 {
          fraction-digits 2;
        }
      units baud ;
      description "baud_rate";
    }
    leaf OSNR{
      type decimal64 {
          fraction-digits 2;
        }
      units dB ;
      description "min required OSNR in 0.1nm (dB)";
    }    
    leaf bit_rate{
      type decimal64 {
          fraction-digits 2;
        }
      units bit/s ;
      description "bit rate";
    }
    leaf roll_off{
      type decimal64 {
          fraction-digits 2;
        }
      description "...";
    }
    leaf cost{
      type decimal64 {
          fraction-digits 2;
        }
      description "arbitrary unit";
    }
  }

   augment /geqpt:Spans{
    container Spans {
      uses Spans ;
    }
  }

     augment /geqpt:Roadms{
    container Roadms {
      uses Roadms ;
    }
  }

     augment /geqpt:SI{
    container SI {
      uses SI ;
    }
  }
}
