module gnpy-spectrum {
  yang-version 1.1;
  namespace "urn:gnpy-spectrum";

  prefix spectrum;

  import gnpy-api {
    prefix "gapi";
    revision-date 2025-06-13;
  }

  import gnpy-eqpt-config {
    prefix "geqpt";
    revision-date 2026-10-29;
  }

  organization
    "Telecom Infra Project OOPT PSE Working Group";
  contact
    "WG Web:   <https://github.com/Telecominfraproject/oopt-gnpy>
     contact:  <mailto:esther.lerouzic@orange.com>
    ";
  description
    "YANG model for gnpy network input for path computation simulation params- 2025";

  revision 2026-10-29 {
    description
      "Stricter checks on equipment config library.";
    reference
      "YANG model for spectrum definition with gnpy";
  }

  grouping spectrum-grouping {
    description
      "Attributes of a spectrum partition.";
    leaf f_min {
      type decimal64 {
        fraction-digits 1;
      }
      mandatory true;
      description
        "Partition definition: f_min is the first carrier central frequency 
        f_max is the last one. partitions must not overlap.
        Note that the meaning of f_min and f_max is different than the one
        in equipment_config SpectralInformation";
    }
    leaf f_max {
      type decimal64 {
        fraction-digits 1;
      }
      must ". >= ./../f_min";
      mandatory true;
      description
        "Partition definition: f_min is the first carrier central frequency 
        f_max is the last one. partitions must not overlap.
        Note that the meaning of f_min and f_max is different than the one
        in equipment_config SpectralInformation";
    }
    leaf slot_width {
      type decimal64 {
        fraction-digits 2;
      }
      mandatory true;
      description "Carrier spectrum occupation. Carriers of this partition
      are spaced at slot_width offsets.";
    }
    leaf delta_pdb {
      type decimal64 {
        fraction-digits 2;
      }
      description "Power offset compared to the reference power used for design
      (SI block in equipment library) to be applied by ROADM to equalize the
      carriers in this partition. Default value is 0 dB.";
    }
    uses geqpt:SI-Transceiver;
    leaf label {
      type string;
      description
        "Unique label that identifies the spectrum partition.";
    }   
  }

  grouping spectrum {
    description
      "Definition of the spectrum to propagate.";
    list spectrum {
      description
        "List of spectrum partitions.";
      key f_min;
      uses spectrum-grouping;
    }
  }

  list spectrum {
    description
      "List of spectrum partitions.";
    key f_min;
    uses spectrum-grouping;
  }

  augment "/gapi:api" {
    description "Add the gnpy-spectrum input in the API request.";
    uses spectrum;
  }
}
