module tip-photonic-topology {
  yang-version 1.1;
  namespace "https://oopt.telecominfraproject.com/yang/topology";
  prefix "tip-topo";

  import tip-photonic-equipment {
    prefix tip-pe;
    revision-date 2020-09-01;
  }

  // import tip-photonic-simulation {
  //   prefix tip-sim;
  //   revision-date 2020-09-01;
  // }

  import ietf-network {
    prefix nw;
    revision-date 2018-02-26;
  }

  import ietf-network-topology {
    prefix nt;
    revision-date 2018-02-26;
  }

  organization "Telecom Infrastructure Project";
  contact "https://github.com/Telecominfraproject/oopt-gnpy";
  description "Network topology for simulating signal propagation via the OOPT-PSE GNPy tool";

  revision 2020-09-01 {
    description "Initial release";
    reference "Internal documentation";
  }

  augment "/nw:networks/nw:network/nw:network-types" {
    description "Telecom Infra Project Open Optical Packet Transport Photonic Simulation Environment";
    container photonic-topology {
      presence "indicates topology describing optical elements";
      description "The presence of this container indicates a topology with optical elements";
    }
  }

  grouping link-common-properties {
    description "Common fiber parameters which are always known, even when performing autodesign and inserting amplifiers";

    leaf type {
      type leafref {
        path "/tip-pe:fiber/tip-pe:type";
      }
      mandatory true;
      description "Fiber type cross-reference";
    }

    leaf length {
      type decimal64 {
        fraction-digits 3;
      }
      units "km";
      mandatory true;
      description "Length of the fiber segment";
    }
  }

  grouping one-amplifier-operating-point {
    description "Amplifier operating regime parameters which map to a one-band amplifier";

    leaf gain-target {
      type tip-pe:gain;
      description "Desired gain of the amplifier

      If not set, GNPy will try to find an optimal operating point.";
    }

    leaf out-voa-target {
      // when "deref(../model)/has-output-voa"; FIXME: implement this
      type tip-pe:db-ratio;
      description "Output VOA setting

      If not set, GNPy will try to find an optimal operating point -- which means operating the EDFA at its highest gain
      for the lowest NF, and using the output VOA to compensate.";
    }

    leaf tilt-target {
      type tip-pe:db-ratio;
      // FIXME: make this available only when the amplifier model supports tilt settings
      description "Desired tilt of the amplifier";
    }

    leaf delta-p {
      type tip-pe:db-ratio;
      description "Per-channel power deviation from the base reference power

      Delta-p expresses the per channel power deviation from the base reference power defined
      in the simulation. For example, if the simulation is set with -1 dBm power, then the
      per-channel power out of amps will be -1 dBm + delta_p of each amp. Delta-p applies
      before the output VOA.

      If the simulation runs in the power_mode, delta-p is used to compute the effective gain,
      and any gain target is ignored. If delta-p is not set, the autodesign will compute one.

      When not in the power_mode, then gain target is used if available, and delta-p is ignored.
      Otherwise, delta-p is used to determine gain.

      Using delta-p and not only gain from a given network and working in power_mode preserves
      individual working points of each amplifier. Instead, using power_mode false and ignoring
      delta-p may lead to error propagation in the power computation across the succession of
      amplifiers if one amp in the chain has a wrong gain reported. Therefore, whenever possible
      the power_mode is recommended.

      If a simulation sets a delta-p target (or a gain target) which exceeds the amplifier's
      maximal power, then the effective per channel power will be reduced in order to fit within
      the amplifier power budget.";
    }
  }

  augment "/nw:networks/nw:network/nt:link" {
    when "../nw:network-types/tip-topo:photonic-topology";
    description "Connections of optical components";

    // Unfortunately, ietf-network-topology has `require-instance: false` for source and target nodes, and
    // the YANG standard doesn't even allow a deviation to override this.
    // Also, a `must` statement is not allowed here, and also not in the `choice` statement. One could do a
    // `when` deviation`, but that one produced non-intuitive error messages.
    // So we have three copies of that superficial `must`, yay.

    choice link-type {
      description "Is this a well-specified fiber, or a link that should be optimized?";

      case tentative-link {
        container tentative-link {
          must "count(deref(../nt:source/nt:source-node)) = 1" {
            error-message "ietf-network-topology:source/source-node must point to a defined node";
          }
          must "count(deref(../nt:destination/nt:dest-node)) = 1" {
            error-message "ietf-network-topology:destination/dest-node must point to a defined node";
          }
          description "A link where GNPy is expected to inject amplifiers where needed";
          uses link-common-properties;
        }
      }

      case fiber {
        container fiber {
          must "count(deref(../nt:source/nt:source-node)) = 1" {
            error-message "ietf-network-topology:source/source-node must point to a defined node";
          }
          must "count(deref(../nt:destination/nt:dest-node)) = 1" {
            error-message "ietf-network-topology:destination/dest-node must point to a defined node";
          }

          description "Fiber connection

          This signifies a fiber whose length is already known. No amplifier huts are available, and the fiber will be used as-is.";

          uses link-common-properties;

          leaf loss-per-km {
            type decimal64 {
              fraction-digits 6;
              range "0..10";
            }
            units "dB/km";
            default 0.2;
            description "Attenuation per kilometer of fiber";
            // FIXME: should we just put total attenuation of that fiber in?
          }

          leaf attenuation-in {
            type tip-pe:db-ratio {
              range "0..100";
            }
            default 0;
            description "Extra fixed attenuator at the beginning of the fiber";
          }

          leaf conn-att-in {
            type tip-pe:db-ratio {
              range "0..100";
            }
            default 0;
            description "Attenuation of the connector at the fiber's beginning";
          }

          leaf conn-att-out {
            type tip-pe:db-ratio {
              range "0..100";
            }
            default 0;
            description "Attenuation of the connector at the fiber's end";
          }

          container raman {
            // must "count(/tip-sim:simulation/tip-sim:nli/tip-sim:raman) = 1" {
            //   error-message "Raman-aware fiber requires a Raman-aware model in global simulation parameters";
            // }

            // must "count(deref(../type)/../tip-pe:raman-efficiency) > 0" {
            //   error-message "Raman simulation requires specification of fiber's Raman efficiency in the equipment library";
            // }

            presence "If present, activate Raman-aware modeling for this fiber";
            description "Raman parameters: SRS awareness and explicit pumping";

            leaf temperature {
              type uint16 {
                range 273..373;
              }
              units "K";
              mandatory true;
              description "Temperature of the fiber";
            }

            list pump {
              key "frequency";

              leaf frequency {
                type tip-pe:frequency-raman-pump;
                mandatory true;
                description "Frequency of this Raman pump laser";
              }

              leaf power {
                type tip-pe:power;
                mandatory true;
                description "Pumping power";
              }

              leaf direction {
                type enumeration {
                  enum co-propagating {
                    description "Co-propagating Raman pump pumps the power in the same direction as the carried optical signal payload";
                  }
                  enum counter-propagating {
                    description "Coounter-propagating Raman pump pumps the power in the opposite direction to the carried optical signal payload";
                  }
                }
                mandatory true;
                description "Direction of propagation of this Raman pump";
              }

              description "Raman pump lasers";
            }
          }
        }
      }

      case patch {
        container patch {
          must "count(deref(../nt:source/nt:source-node)) = 1" {
            error-message "ietf-network-topology:source/source-node must point to a defined node";
          }
          must "count(deref(../nt:destination/nt:dest-node)) = 1" {
            error-message "ietf-network-topology:destination/dest-node must point to a defined node";
          }

          // FIXME: check booster/preamp restrictions for ROADMs

          description "Direct connection between network elements

          A direct patch cord is a special case of fiber. It is assumed to be very short (a hundred meters at most) so that the
          effect of NLI is limited, and that there's negligible attenuation.";

          leaf roadm-target-egress-per-channel-power {
            when "count(deref(../../nt:source/nt:source-node)/../roadm) > 0";
            type tip-pe:power;
            description "Per-channel tar egress power for signals exiting the ROADM over this link";
          }
        }
      }
    }
  }

  augment "/nw:networks/nw:network/nw:node" {
    when "../nw:network-types/tip-topo:photonic-topology";
    description "Optical elements within a network";

    choice element {
      mandatory true;
      description "A physical instance of something";

      case amplifier-placeholder {
        leaf amplifier-placeholder {
          type empty;
          mandatory true;
          description "Intent to place an amplifier, to be replaced by GNPy's autodesign with a specific model";
        }
      }

      case amplifier {
        container amplifier {
          description "Amplifier";

          leaf model {
            type leafref {
              path "/tip-pe:amplifier/tip-pe:type";
            }
            mandatory true;
            description "Amplifier model cross-reference";
          }

          uses one-amplifier-operating-point {
            when "count(deref(model)/multiband) = 0";
          }

          list per-band {
            when "count(deref(../model)/multiband) = 1";
            leaf model {
              type leafref {
                path "/tip-pe:amplifier/tip-pe:type";
              }
              must "count(deref(../../model)/multiband/amplifiers[. = current()]) = 1" {
                error-message "Per-band amplifier data refer to wrong subamplifier definition";
              }
              description "Sub-amplifier model cross-reference";
            }
            key "model";
            uses one-amplifier-operating-point;
            description "Per-subamplifier operating parameters";
          }
        }
      }

      case attenuator {
        container attenuator {
          description "Excessive attenuation

          Use this construct for slicing together longer segments of fiber. For shorter connections,
          use an `nt:link` with a `patch`. Do not put an `attenuator` in between of two `nt:link`, `patch` connections.";

          leaf attenuation {
            type tip-pe:db-ratio;
            default 0;
            description "Attenuator loss";
          }
        }
      }

      case transceiver {
        container transceiver {
          description "Transceiver";

          leaf model {
            type leafref {
              path "/tip-pe:transceiver/tip-pe:type";
            }
            mandatory true;
            description "Transceiver model, a cross-reference to the equipment library";
          }
        }
      }

      case roadm {
        container roadm {
          description "ROADM";

          leaf model {
            type leafref {
              path "/tip-pe:roadm/tip-pe:type";
            }
            mandatory true;
            description "ROADM model, a cross-reference to the equipment library";
          }

          leaf target-egress-per-channel-power {
            type tip-pe:power;
            description "Per-channel target egress power for signals exiting the ROADM

            This can be overriden on a per-link basis via patch/roadm-target-egress-per-channel-power.";
          }
        }
      }

    }
  }
}
