module tip-photonic-simulation {
  yang-version 1.1;
  namespace "https://oopt.telecominfraproject.com/yang/simulation";
  prefix "tip-sim";

  import tip-photonic-equipment {
    prefix tip-pe;
    revision-date 2020-09-01;
  }

  organization "Telecom Infrastructure Project";
  contact "https://github.com/Telecominfraproject/oopt-gnpy";
  description "Simulation settings for GNPy";

  revision 2020-09-01 {
    description "Initial release";
    reference "Internal documentation";
  }

  container simulation {
    presence "Activates a GNPy simulation";
    description "Simulation settings and per-run input parameters";

    choice spectrum {
      mandatory true;
      description "Spectral load for planning considerations

      This is the channel allocation for which GNPy will optimize. It should represent the end-of-life spectrum allocation.";

      case grid {
        container grid {
          description "Homogeneous channel allocation on a fixed grid";

          leaf frequency-min {
            type tip-pe:carrier-frequency;
            default 191.35;
            description "Central frequency of the first (lowest) channel";
          }

          leaf frequency-max {
            type tip-pe:carrier-frequency;
            default 196.1;
            description "Central frequency of the last (highest) channel";
          }

          leaf spacing {
            type tip-pe:frequency-channel-spacing;
            default 50.0;
            description "Grid spacing";
          }

          leaf baud-rate {
            type tip-pe:baud-rate;
            mandatory true;
            description "Symbol baud rate";
          }

          leaf tx-osnr {
            type tip-pe:db-ratio;
            mandatory true;
            description "Transponder TX signal OSNR";
          }

          leaf tx-roll-off {
            type tip-pe:roll-off;
            mandatory true;
            description "Roll-off parameter (β) of the TX pulse shaping filter. This assumes a raised-cosine filter.";
          }

          leaf power {
            type tip-pe:power;
            mandatory true;
            description "";
          }
        }
      }
    }

    container autodesign {
      description "Optimization parameters";

      choice edfa-gain-strategy {
        mandatory true;
        description "Optimization strategy for setting amplifier operating mode";

        case power-mode {
          container power-mode {
            description "Whatever GNPy power-mode actually means"; // FIXME

            container power-sweep {
              presence "Vary the initial launch power";
              description "Varying the initial launch power";

              leaf start {
                type tip-pe:db-ratio;
                mandatory true;
                description "Initial delta from the reference power when determining the best initial launch power";
              }
              leaf stop {
                type tip-pe:db-ratio;
                mandatory true;
                description "Final delta from the reference power when determining the best initial launch power";
              }
              leaf step-size {
                type tip-pe:db-ratio;
                mandatory true;
                description "Step size when determining the best initial launch power";
              }
            }
          }
        }

        case gain-mode {
          leaf gain-mode {
            type empty;
            mandatory true;
            // FIXME: describe this
            description "Set EDFA gain based on previous span loss

            For all EDFAs whose gain has not been set manually, set the gain based on the following rules:

            1) Set gain to the preceding span loss.

            2) Offset the gains around the reference power (FIXME: what does it mean?

            This will leave the gain of EDFAs which have their gains set manually in the network topology unchanged.";
          }
        }
      }

      container power-adjustment-for-span-loss {
        description "Adjusting launch power depending on a span loss

        When in effect, lanuch powers to spans are adjusted based on the total span loss. The span loss is
        compared to a reference span of 20dB, and the launch power is adjusted by about 0.3 * loss_difference,
        up to a provided maximal adjustment.

        This adjustment is performed for all spans when running in the `power-mode`. When in `gain-mode`,
        it affects only EDFAs which do not have an explicitly assigned `delta-p`.
        ";

        leaf maximal-reduction {
          type tip-pe:power;
          mandatory true;
          description "Launch power might be reduced by up to this many dB on \"short\" spans";
        }

        leaf maximal-boost {
          type tip-pe:power;
          mandatory true;
          description "Launch power might be increased by up to this many dB on lossy spans";
        }

        leaf excursion-step-size {
          type tip-pe:power;
          mandatory true;
          description "Step size when increasing/decreasing the launch power";
        }
      }

      leaf-list allowed-inline-edfa {
        type leafref {
          path "/tip-pe:amplifier/tip-pe:type";
        }
        description "Allowed EDFA types to be used as inline amplifiers";
      }

      leaf maximal-span-length {
        type uint16 {
          range 10..300;
        }
        units "km";
        default 100;
        description "Distance threshold for inserting amplifiers into tentative links

        When working with not-fully-specified fiber links (tentative links), keep the individual fiber below this length. Extra
        inline amplifiers will be automatically inserted in between.";
      }
    }

    leaf system-margin {
      type tip-pe:power {
        range 0..10;
      }
      default 2;
      description "Require this many dBm of GSNR headroom as a safety margin for End-of-Life component deterioration";
    }

    leaf edfa-maximal-extended-power {
      type tip-pe:power {
        range 0..6;
      }
      default 2.5;
      status deprecated; // FIXME: move this into /tip-photonic-equipment:amplifier once the backend accounts for that argument
      description "Allow up to this many dB increase of an amplifier's gain into its extended power range";
    }

    leaf shortest-span-without-extra-attenuation {
      type tip-pe:db-ratio;
      default 10.0;
      description "When a fiber span has a lower attenuation than this, automatically insert an attenuator at its beginning";
    }

    container nli {
      description "Non-linear interference (NLI) simulation options";

      leaf algorithm {
        type enumeration {
          enum analytic-gn-model {
            description ""; // FIXME: to be filed by Polito
          }
          enum generalized-gn-spectrally-separated {
            description ""; // FIXME: to be filed by Polito
          }
        }
        default generalized-gn-spectrally-separated;
        description "What simulation model to use for calculating NLI contribution to the GSNR";
      }

      container raman {
        presence "If present, enable Raman-aware simulation";
        description "Global options for Raman-aware simulation";
        // FIXME: this really needs docs! CHeck with Alessio and Andrea et al
        // FIXME: space-resolution
      }

      // FIXME: grid-size
      // FIXME: dispersion-tolerance
      // FIXME: phase-shift-tolerance
      // FIXME: computed-channels
    }
  }

  augment "/tip-pe:transceiver/tip-pe:mode" {
    description "Transponder mode selection: cost of a particular mode";

    leaf cost {
      type uint32;
      units "Arbitrary units";
      default 1;
      description "Cost of selecting this mode when determining path feasibility";
    }
  }
}
