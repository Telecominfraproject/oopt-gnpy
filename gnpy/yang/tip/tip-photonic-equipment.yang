module tip-photonic-equipment {
  yang-version 1.1;
  namespace "https://oopt.telecominfraproject.com/yang/equipment";
  prefix "tip-pe";

  organization "Telecom Infrastructure Project";
  contact "https://github.com/Telecominfraproject/oopt-gnpy";
  description "Catalog of photonic equipment for simulating signal propagation via the OOPT-PSE GNPy tool";

  revision 2023-09-01 {
    description "Initial release";
  }

  typedef db-ratio {
    type decimal64 {
      fraction-digits 2;
    }
    units "dB";
    description "Decibels";
  }

  typedef noise-figure {
    type db-ratio {
      range "3.0 .. 20.0";
    }
    description "Noise Figure of an amplifier";
  }

  typedef gain {
    type db-ratio {
      range "0 .. 40.0";
    }
    description "Gain of an amplifier";
  }

  typedef power {
    type decimal64 {
      fraction-digits 2;
      range "-99.9 .. 30.0";
    }
    units "dBm";
    description "Optical power in dBm";
  }

  typedef pump-frequency {
    type decimal64 {
      fraction-digits 7;
      range "180.0 .. 220.0";
    }
    units "THz";
    description "Optical frequency of a pump";
  }

  typedef carrier-frequency {
    type decimal64 {
      fraction-digits 7;
      range "184.0 .. 198.0";
    }
    units "THz";
    description "Optical frequency of a signal

    This is the central frequency of a signal. It is different from `edge-frequency`
    which refers to the edges of the usable passband.";
  }

  typedef edge-frequency {
    type decimal64 {
      fraction-digits 7;
      range "184.0 .. 198.0";
    }
    units "THz";
    description "Edge frequency of the frequency band that the signal can occupy.

    This is different from `carrier-frequency` (which refers to the center of the signal). This
    parameter refers to the edge of the occupied frequency band.";
  }

  typedef frequency-channel-spacing {
    type decimal64 {
      fraction-digits 7;
      range "6.25 .. 200.0";
    }
    units "GHz";
    description "Channel spacing";
  }

  typedef baud-rate {
    type decimal64 {
      fraction-digits 4;
      range "10 .. 1000";
    }
    units "Gbaud";
    description "Symbol rate";
  }

  typedef roll-off {
    type decimal64 {
      fraction-digits 4;
      range "0 .. 1";
    }
    description "Roll-off parameter (β) of the TX pulse shaping filter. This assumes a raised-cosine filter.";
  }

  typedef cd {
    type decimal64 {
      fraction-digits 2;
      // No range, because we don't know what various vendors have implemented (and this parameter is only really
      // used for describing the transponder performance.
    }
    units "ps × nm⁻¹";
    description "Chromatic Dispersion (CD).";
  }

  typedef fiber-chromatic-dispersion {
    type decimal64 {
      fraction-digits 6;
      range "-25 .. 25";
    }
    units "ps × nm⁻¹ × km⁻¹";
  }

  typedef fiber-chromatic-dispersion-slope {
    type decimal64 {
      fraction-digits 8;
      // FIXME: Andrea: this range is wrong
      // range "0 .. 0.1";
    }
    units "ps × nm⁻² × km⁻¹";
  }

  typedef pmd {
    type decimal64 {
      fraction-digits 4;
    }
    units "ps";
    description "Polarization mode dispersion (PMD).";
  }

  typedef pdl {
    type db-ratio {
      range "0 .. 20";
    }
    description "Largest difference in loss occuring at all states of polarization.";
  }

  typedef psd {
    type decimal64 {
      fraction-digits 8;
    }
    units "dBm × GHz⁻¹";
    description "Power Spectral Density, optical power per some spectral width";
  }

  typedef polynomial-coefficient {
    type decimal64 {
      fraction-digits 12;
    }
    description "One coefficient within a polynomial";
  }

  typedef automatic-default {
    type enumeration {
      enum automatic-default {
        description "The default value is inferred by GNPy based on other values, internal heuristics, and empirical data";
      }
    }
  }

  grouping cubic-polynomial-coefficients {
    description "Coefficients for a polynomial of a third degree: f(x) = a*x³ + b*x² + c*x + d";
    leaf a {
      type polynomial-coefficient;
      mandatory true;
      description "Cubic (x³) coefficient";
    }
    leaf b {
      type polynomial-coefficient;
      mandatory true;
      description "Quadratic (x²) coefficient";
    }
    leaf c {
      type polynomial-coefficient;
      mandatory true;
      description "Linear (x) coefficient";
    }
    leaf d {
      type polynomial-coefficient;
      mandatory true;
      description "Offset (+) coefficient";
    }
  }

  grouping amp-spectrum-profile {
    description "Changes in amplifier's operation as a function of frequency";

    list gain-ripple {
      leaf frequency {
        type edge-frequency;
        description "Frequency for the specific gain ripple deviation";
      }

      leaf gain-ripple {
        type db-ratio;
        mandatory true;
        description "Gain ripple deviation at a given frequency";
      }

      key "frequency";

      description "Amplifier gain ripple excursion comb list in dB across the frequency range";
    }

    list nf-ripple {
      leaf frequency {
        type edge-frequency;
        description "Frequency for the specific NF ripple deviation";
      }

      leaf nf-ripple {
        type db-ratio;
        mandatory true;
        description "NF ripple deviation at a given frequency";
      }

      key "frequency";

      description "Amplifier NF ripple excursion comb list in dB across the frequency range";
    }

    list dynamic-gain-tilt {
      leaf frequency {
        type edge-frequency;
        description "Frequency for the specific NF ripple deviation";
      }

      leaf dynamic-gain-tilt {
        type db-ratio;
        mandatory true;
        description "DGT at a specified frequency";
      }

      key "frequency";

      description "Dynamic Gain Tilt (DGT) refers to a relative change of gain
      at a given frequency when compared to a reference frequency.

      Intro about the model: https://telecominfraproject.workplace.com/groups/OOPT.PSE/permalink/957144244450445/
      Relevant paper: https://www.osapublishing.org/jlt/abstract.cfm?uri=JLT-18-3-343";
    }
  }

  grouping amp-common {
    description "Properties common to all EDFAs except the cascaded models";

    leaf frequency-min {
      type edge-frequency;
      default 191.325;
      description "Minimal frequency supported by this amplifier

      This refers to the edge of the optical spectrum, not to a central frequency of a fixed grid.";
    }

    leaf frequency-max {
      type edge-frequency;
      default 196.125;
      description "Maximal frequency supported by this amplifier

      This refers to the edge of the optical spectrum, not to a central frequency of a fixed grid.";
    }

    leaf has-output-voa {
      type boolean;
      default false;
      description "If true, output VOA is present.

      An amplifier with an output VOA can be pushed to operate at its max-power-out if the output VOA is available.";
    }

    leaf gain-flatmax {
      type gain;
      mandatory true;
      description "Maximal gain of the nominal range (without entering the extended range)

      Once the amplifier's gain gets pushed into the extended range, it begins to tilt as specified in the dynamic-gain-tilt.";
    }

    leaf max-power-out {
      type power;
      mandatory true;
      description "Maximal output power at the amplifier's output port

      The total signal output power will not be allowed beyond this value.";
    }
  }


  list amplifier {
    key "type";
    description "Available amplifier (EDFA) models";

    leaf type {
      type string;
      description "Brief identification of the amplifier model. This is used for cross-referencing from topology data.";
    }

    uses amp-common {
      when "count(cascaded) = 0";
      description "Common parameters for all EDFAs except aggregated ones";
    }

    leaf gain-min {
      type gain;
      mandatory true;
      description "Minimal possible gain of the amplifier

      If the amplifier's gain is set below this value, the amplifier's input is automatically padded with an attenuator,
      and the NF is increased by the attenuation of this padding.";
    }

    choice noise-model {
      mandatory true;
      description "What simulation algorithm to use for this amplifier model";

      case polynomial-NF {
        container polynomial-NF {
          description "Whitebox model with detailed information about gain ripple, NF ripple and dynamic gain tilt

          Polynomial coefficients for NF calculation:

            f(x) = a*x³ + b*x² + c*x + d

            NF = f(gain - gain_max)

          This model can be also used for fixed-gain fixed-NF amplifiers. In that case, use:

            a = b = c = 0
            d = NF

          Note that pre-YANG GNPy releases would use NF = f(gain_max - gain) here (i.e., negative sign).";

          uses cubic-polynomial-coefficients;
        }
      }

      case min-max-NF {
        container min-max-NF {
          description "Operator-focused model

          Performance is defined by the minimal and maximal NF. These are especially suited to model a dual-coil
          EDFA with a VOA in between.";

          leaf nf-min {
            type noise-figure;
            mandatory true;
            description "Minimal Noise Figure (operating at the point of the maximal flat gain)

            See gain-flatmax.";
          }

          leaf nf-max {
            type noise-figure;
            mandatory true;
            description "Maximal Noise Figure (operating at the minimal gain)";
          }
        }
      }

      case OpenROADM-ILA {
        container OpenROADM-ILA {
          description "EDFA model based on the OpenROADM specification for an ILA

          OpenROADM describes amplifier performance in terms of an incremental OSNR as a function of input power:

            Incremental OSNR = a*Pᵢₙ³ + b*Pᵢₙ² + c*Pᵢₙ + d
          ";

          uses cubic-polynomial-coefficients;
        }
      }

      case OpenROADM-preamp {
        container OpenROADM-preamp {
          presence true;
          description "Linear impairments of the MW-MW path within an OpenROADM ROADM node

          Unlike GNPy which simulates the preamplifier and the booster separately as two amplifiers for best accuracy,
          the OpenROADM specification mandates a certain performance level for a combination of these two amplifiers.
          For the express path, the effective noise mask comprises the preamplifier and the booster.
          When terminating a channel, the same effective noise mask is mandated for a combination of the preamplifier
          and the drop stage.

          This NF model provides all of the linear impairments to the signal, including those which are incurred by
          the booster in a real network.";
        }
      }

      case OpenROADM-booster {
        container OpenROADM-booster {
          presence true;
          description "A faux, \"zero-noise\" amplifier for use along with OpenROADM-preamp as a booster.";
        }
      }

      case cascaded {
        container cascaded {
          description "Dual-stage amplifier combines two distinct amplifiers

          The first amplifier will be always operated at its maximal gain (and therefore its best NF).";

          leaf preamp {
            type leafref {
              path "/tip-pe:amplifier/type";
            }
            must "count(deref(.)/../cascaded) = 0" {
              error-message "First (preamp) stage of a cascaded amplifier cannot be a cascaded amplifier";
            }
            must "../../gain-min >= deref(.)/../gain-min" {
              error-message "Minimal total gain of a cascaded EDFA cannot be lower that the minimal gain of the preamp";
            }
            mandatory true;
            description "Amplifier type used as a preamplifier, i.e., the first stage";
          }

          leaf booster {
            type leafref {
              path "/tip-pe:amplifier/type";
            }
            must "count(deref(.)/../cascaded) = 0" {
              error-message "Second (booster) stage of a cascaded amplifier cannot be a cascaded amplifier";
            }
            must "(deref(.)/../frequency-min <= deref(../preamp)/../frequency-max) and
                  (deref(.)/../frequency-max >= deref(../preamp)/../frequency-min)" {
              error-message "booster/preamp operating frequencies do not overlap";
            }
            mandatory true;
            description "Amplifier type used as a booster, i.e., the second stage";
          }
        }
      }

      case raman-approximation {
        container raman-approximation {
          description "Emulate a Raman amplifier with a possibly negative NF

          This NF model assumes a particular, fixed NF. It is similar to the polynomial-NF model, except that the
          effective NF value is fixed (and therefore it does not vary with the amplifier's operating point), and
          that the effective NF can be described as a negative value.

          Use this for model to (roughly) emulate a Raman amplifier when the detailed description of Raman pumps
          is not available from the equipment vendor.";

          leaf nf {
            type db-ratio {
              range "-5.0 .. 20.0";
            }
            mandatory true;
            description "Noise Figure (NF) of the amplifier";
          }
        }
      }
    }

    uses amp-spectrum-profile {
      when "count(cascaded) = 0";
    }

    leaf polarization-mode-dispersion {
      type pmd {
        range "0 .. 5";
      }
      default 0;
      description "Polarization Mode Dispersion (PMD) of the amplifier";
    }

    leaf polarization-dependent-loss {
      type pdl {
        range "0 .. 5";
      }
      default 0;
      description "Polarization Dependent Loss (PDL) of the amplifier";
    }


    leaf model-precision {
      type enumeration {
        enum public-approximation {
          description "These data come from a publicly available datasheet, and as such might be only an approximate representation";
        }
        enum reasonably-precise {
          description "The GNPy team believes that these are reasonably accurate";
        }
      }
      default reasonably-precise;
      description "How precise are the modeling data

      If a simulation runs with only approximate inputs, the simulation results might be \"tainted\" with inaccuracies.";
    }
  }


  list fiber {
    key "type";
    description "Available fiber types";

    leaf type {
      type string;
      description "Unique identification of the fiber type. This is used for cross-referencing from topology data.";
    }

    leaf effective-area {
      type union {
        type automatic-default;
        type decimal64 {
          fraction-digits 2;
          range "1 .. 200";
        }
      }
      units "μm²";
      default automatic-default;
      description "Effective area of the fiber (not just the MFD circle), A_eff

      When not provided, the value is computed based on `gamma`, if that one is provided explicitly, otherwise 83 μm² is assumed.

      Cf. Corning whitepaper on MFD/EA: https://www.corning.com/microsites/coc/oem/documents/specialty-fiber/WP7071-Mode-Field-Diam-and-Eff-Area.pdf";
      reference "https://www.corning.com/microsites/coc/oem/documents/specialty-fiber/WP7071-Mode-Field-Diam-and-Eff-Area.pdf";
    }

    leaf gamma {
      type union {
        type automatic-default;
        type decimal64 {
          fraction-digits 8;
          // FIXME: Andrea: the code uses 0 if no value is given, yet this range is different
          // range "0.5 .. 2.5";
        }
      }
      units "W⁻¹ × km⁻¹";
      default automatic-default;
      description "Fiber's γ coefficient

      When not provided, this value is determined from the `effective-area`, if that one is provided explicitly.
      In case neither is set, then a default value of 0 applies.

      See, e.g., A. Carena, G. Bosco, V. Curri, P. Poggiolini, M. Tapia Taiba, and F. Forghieri. Statistical characterization
      of PM-QPSK signals after propagation in uncompensated fiber links. In European Conference on Optical Communications,
      2010, 1–3. IEEE, 2010-09.";

      reference "http://ieeexplore.ieee.org/document/5621509/";
    }

    leaf pmd-coefficient {
      type decimal64 {
        fraction-digits 10;
        range "0 .. 10";
      }
      units "ps × √(km)⁻¹";
      mandatory true;
      description "Polarization mode dispersion (PMD) coefficient";
    }

    list per-frequency {
      description "Optical properties which might vary with frequency";
      key "frequency";

      leaf frequency {
        type pump-frequency;
      }

      leaf chromatic-dispersion {
        type fiber-chromatic-dispersion;
        description "Chromatic dispersion";
      }

      leaf chromatic-dispersion-slope {
        type fiber-chromatic-dispersion-slope;
        default "0.07";
        description "Chromatic dispersion slope is related to the β₃ coefficient

        Cf. Abramczyk, Halina. Dispersion phenomena in optical fibers. Virtual European University on Lasers, 2005.";

        reference "http://mitr.p.lodz.pl/evu/lectures/Abramczyk3.pdf";
      }

      must "count(chromatic-dispersion) > 0" {
        error-message "Chromatic Dispersion (CD) must be provided";
      }
    }

    container raman-coefficient {
      description "Characteristics of the power transfer between channels during propagation";
      reference "https://doi.org/10.1109/JLT.2022.3162134";
      presence "If present, this fiber type can consider the Rama effect during propagation.";

      leaf reference-frequency {
        type pump-frequency;
        description "Frequency of a pump to which the `gamma-efficiency` parameters are referenced

        The default value corresponds to the pump wavelength of 1454 nm.";
      }

      list gamma-efficiency {
        key "delta-frequency";
        description "Efficiency of Raman amplification in the fiber medium per operating frequency

        See, e.g., J. Bromage. Raman Amplification for Fiber Communications Systems. In J. Lightwave Technol.  22, 79- (2004).";
        reference "";

        min-elements 1;

        leaf delta-frequency {
          type decimal64 {
            fraction-digits 3;
            range "0 .. 60";
          }
          units "THz";
          description "Spectral difference between the pump frequency and the specific Stokes wave";
        }

        leaf g_0 {
          type decimal64 {
            fraction-digits 12;
            range "0 .. 1";
          }
          mandatory true;
          description "Raman gain coefficient in terms of mode intensity";
        }
      }
    }
  }


  list transceiver {
    key "type";
    description "Available transceivers";

    leaf type {
      type string;
      description "Unique identification of the transceiver type. This is used for cross-referencing from topology data.";
    }

    leaf laser-frequency-min {
      type carrier-frequency;
      default 191.35;
      description "Minimal central frequency supported by this transceiver model";
    }

    leaf laser-frequency-max {
      type carrier-frequency;
      default 196.125;
      description "Maximal central frequency supported by this transceiver model";
    }

    list mode {
      key "name";
      min-elements 1;
      description "Operating mode of a transceiver";

      leaf name {
        type string;
        description "Name of this operating mode";
      }

      leaf bit-rate {
        type uint16 {
          range "100 .. 1000";
        }
        units "Gbits * s⁻¹";
        description "Data bit rate";
      }

      leaf baud-rate {
        type baud-rate;
        mandatory true;
        description "Symbol baud rate";
      }

      leaf required-osnr {
        type db-ratio {
          range "10..40";
        }
        mandatory true;
        description "Minimal required OSNR at the Rx port per 0.1nm of bandwidth";
      }

      leaf in-band-tx-osnr {
        type db-ratio;
        description "Worst-case guaranteed initial OSNR at the Tx port per 0.1nm of bandwidth

        Only the in-band OSNR is considered.";
        default 50.0;
      }

      leaf grid-spacing {
        type frequency-channel-spacing;
        mandatory true;
        description "Minimal grid spacing

        This includes the effective channel spectral bandwidth as well as any operational constraints and policies.";
      }

      leaf tx-roll-off {
        type roll-off;
        default 0.15;
        description "Roll-off parameter (β) of the TX pulse shaping filter. This assumes a raised-cosine filter.";
      }

      leaf max-chromatic-dispersion {
        type cd;
        description "Maximal allowed CD (a hard limit)";
      }

      leaf max-polarization-mode-dispersion {
        type pmd {
          range "0 .. 500";
        }
        description "Maximal allowed PMD (a hard limit)";
      }

      leaf max-polarization-dependent-loss {
        type pdl;
        description "Maximal allowed PDL (a hard limit)";
      }

      list penalties {
        key "chromatic-dispersion polarization-mode-dispersion polarization-dependent-loss";

        leaf chromatic-dispersion {
          type cd;
          must ". <= ../../max-chromatic-dispersion" {
            error-message "CD in the penalty matrix exceeds receiver tolerance";
          }
          description "CD which (when combined with other values, if provided) yields a given penalty";
        }

        leaf polarization-mode-dispersion {
          type pmd {
            range "0 .. 500";
          }
          must ". <= ../../max-polarization-mode-dispersion" {
            error-message "PMD in the penalty matrix exceeds receiver tolerance";
          }
          description "PMD which (when combined with other values, if provided) yields a given penalty";
        }

	leaf polarization-dependent-loss {
          type pdl;
          must ". <= ../../max-polarization-dependent-loss" {
            error-message "PDL in the penalty matrix exceeds receiver tolerance";
          }
          description "PDL which (when combined with other values, if provided) yields a given penalty";
	}

        leaf penalty {
          type db-ratio {
            range "-5 .. 10";
          }
          mandatory true;
          description "Resulting GSNR penalty at the specified CD, PMD and PDL";
        }

        description "GSNR penalty for a combination of a CD, PMD and PDL

        The receiver performance should be de-rated by a given `penalty` for a specified combination of CD, PMD and PDL.
        GNPy will use linear approximation between the provided datapoints in the CD/PMD/PDL matrix.
        ";
      }
    }
  }


  list roadm {
    key "type";
    description "ROADM - Reconfigurable Optical Add/Drop Multiplexer";

    leaf type {
      type string;
      description "Unique identification of the transponder type. This is used for cross-referencing from topology data.";
    }

    leaf add-drop-osnr {
      type db-ratio;
      mandatory true;
      description "OSNR penalty introduced by the Add stage and the Drop stage of this ROADM model

      Effective degradation of the signal, taking into account both the Add and the Drop stages of this ROADM model.";
    }

    choice equalization-strategy {
      case per-channel-output-power {
        leaf per-channel-output-power {
          type power;
          description "Target power output for each channel";
          mandatory true;
        }
      }
      case power-spectral-density {
        leaf power-spectral-density {
          type psd;
          description "Target power per channel's symbol rate

          This strategy computes the target power based on just this signal's properties, disregarding the frequency grid or channel spacing used by the ROADMs.

          This is different from the `power-by-dwdm-slot-width` which computes the power based on the assigned passband slot width.";
          mandatory true;
        }
      }
      case power-by-dwdm-slot-width {
        leaf power-by-dwdm-slot-width {
          type psd;
          description "Target power per channel's slot width allocation

          This strategy computes the target power based on the assigned slot width. The actual signal's Baud rate is ignored.
          This is different from the `power-spectral-density` which ignores the frequency grid or channel spacing.";
          mandatory true;
        }
      }
      mandatory true;
    }

    leaf polarization-mode-dispersion {
      type pmd {
        range "0 .. 5";
      }
      default 0;
      description "Polarization mode dispersion (PMD) of the express path within this ROADM model";
    }

    leaf polarization-dependent-loss {
      type pdl {
        range "0 .. 5";
      }
      default 0;
      description "Polarization Dependent Loss (PDL) of the express path within this ROADM model";
    }

    leaf-list compatible-preamp {
      type leafref {
        path "/tip-pe:amplifier/type";
      }
      description "A set of allowed amplifier types to be used in the ingress direction

      If empty, autodesign is allowed to pick any amplifier as a preamp.";
    }

    leaf-list compatible-booster {
      type leafref {
        path "/tip-pe:amplifier/type";
      }
      description "A set of allowed amplifier types to be used in the egress direction

      If empty, autodesign is allowed to pick any amplifier as a booster.";
    }

  }

}
